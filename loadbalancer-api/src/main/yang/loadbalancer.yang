module loadbalancer {

    yang-version 1;

    namespace
      "http://netconfcentral.org/ns/loadbalancer";

    prefix lb;

    organization "Netconf Central";

    contact
      "Federico Cimorelli <cimorelli@dis.uniroma1.it>";

    description
      "YANG version of the ODL LOADBALANCER.";

    revision "2015-09-01" {
      description
        "OpenDaylight Loadbalancer module.";
    }


    container loadbalancer {
      presence
        "Indicates the loadbalancer service is available";
      description
        "Top-level container for all loadbalancer database objects.";

      leaf loadbalancerStatus {
        type enumeration {
          enum "up" {
            value 1;
            description
              "The loadbalancer knob position is up.
                      No lb is being made now.";
          }
          enum "down" {
            value 2;
            description
              "The loadbalancer knob position is down.
                      Toast is being made now.";
          }
        }
        config false;
        mandatory true;
        description
          "This variable indicates the current state of
               the loadbalancer.";
      }

      leaf loadbalancerInputParamOne {
        type uint32;
        config true;
        default 100;
        description
          "Parameter loadbalancerInputParamOne's descroption";
      }
    }


    rpc start-loadbalancer{
        description "Start loadbalancer algorithm";
        input {
            leaf loadbalancerInputParamOne{
                type uint32;
                description "Loadbalancer first input parameter";
                default 100;
                }
            }
        output {
            leaf response-code {
                type uint32;
                description "Response code, 0 ok, <0 ko";
                default 0;
                }
            leaf response-message{
                type string;
                description "Response message";
                default "ND";
            }
        }
    }


    rpc stop-loadbalancer{
        description "Stop loadbalancer algorithm";
        output {
            leaf response-code {
                type uint32;
                description "Response code, 0 ok, <0 ko";
                default 0;
                }
            }
        }


    rpc get-loadbalancer-status{
        description "Return the status of the loadbalancer";
        output {
            leaf response-code {
                type uint32;
                description "Response code, 1 UP, 0 DOWN, <0 ERROR";
                default 0;
                }
            }
        }


    rpc set-switch-role{
        description "Sets the role on the switch ids in input";
        input {
            leaf ofp-role{
                type uint32;
                description "The role to be triggered (1:OFPxyz, 2:OFP...)";
                default 1;
                }
            leaf-list switch-ids{
                type string;
                description "The switches of interest";
                min-elements 1;
            }
        }
        output {
            leaf response-code {
                type uint32;
                description "Response code, 0 ok, <0 ko";
                default 0;
                }
            leaf response-message{
                type string;
                description "Response message";
                default "ND";
            }
        }
    }


    rpc get-switch-role{
        description "Returns the role on the switch ids in input";
        input {
            leaf-list switch-ids{
                type string;
                description "The switches of interest";
                min-elements 1;
            }
        }
        output {
            leaf response-code {
                type uint32;
                description "Response code, 0 ok, <0 ko";
                default 0;
                }
            leaf-list response-message{
                type string;
                description "Response message in 'dpID:role' format";
                default "ND";
            }
        }
    }

  }
